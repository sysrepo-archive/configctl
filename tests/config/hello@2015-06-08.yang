module hello {
  namespace "urn:ietf:params:xml:ns:yang:hello";
  prefix ob;

  description
    "hello world";
  contact
    "mislav.novakovic@sartura.hr";

  revision 2015-06-08 {
    description
      "Inital revision";
  }

  container hello {
    leaf foo {
      type string;
    }
    leaf bar {
      type int32;
    }
    leaf toto {
      type string;
    }
    leaf number {
      type int32;
    }
    leaf number8 {
      type int8;
    }
    list person {
      key "name name2";
      leaf "name" {
        type "string";
      }
      leaf "name2" {
        type "string";
      }
      leaf "age" {
        type "int32";
      }
    }
    container numbers {
      leaf number_8 {
        type int8;
      }
      leaf number_16 {
        type int16;
      }
      leaf number_32 {
        type int32;
      }
      leaf number_64 {
        type int64;
      }
      leaf number_u8 {
        type uint8;
      }
      leaf number_u16 {
        type uint16;
      }
      leaf number_u32 {
        type uint32;
      }
      leaf number_u64 {
        type uint64;
      }
      leaf new_number_8 {
        type int8;
      }
      leaf new_number_16 {
        type int16;
      }
      leaf new_number_32 {
        type int32;
      }
      leaf new_number_64 {
        type int64;
      }
      leaf new_number_u8 {
        type uint8;
      }
      leaf new_number_u16 {
        type uint16;
      }
      leaf new_number_u32 {
        type uint32;
      }
      leaf new_number_u64 {
        type uint64;
      }
    }
  }
}
